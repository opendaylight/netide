module main-impl {
    yang-version 1;
    namespace "urn:opendaylight:params:xml:ns:yang:netide:main-impl";
    prefix "main-impl";

    import config { prefix config; revision-date 2013-04-05; }
    import opendaylight-md-sal-binding { prefix md-sal-binding; revision-date 2013-10-28;}

    description
        "Service definition for hello project";

    revision "2015-10-01" {
        description
            "Initial revision";
    }

    identity main-impl {
        base config:module-type;
        config:java-name-prefix NetideMain;
    }

    augment "/config:modules/config:module/config:configuration" {
        case main-impl {
            when "/config:modules/config:module/config:type = 'main-impl'";
            
            leaf core-port {
                type int32;
                config true;
            }
            
            container broker {
                uses config:service-ref {
                    refine type {
                        mandatory true;
                        config:required-identity md-sal-binding:binding-broker-osgi-registry;
                    }
                }
            }
        }
        
    }
}
