/*
 * Copyright (c) 2015 NetIDE Consortium and others.  All rights reserved.
 *
 * This program and the accompanying materials are made available under the
 * terms of the Eclipse Public License v1.0 which accompanies this distribution,
 * and is available at http://www.eclipse.org/legal/epl-v10.html
 */
module netide {
    yang-version 1;
    namespace "urn:opendaylight:params:xml:ns:yang:netide";
    prefix "netide";

    revision "2015-10-01" {
        description "Initial revision of netide model";
    }
    
    rpc status {
        output {
            leaf netip-version {
                type int8;
            }
            leaf-list of-versions {
                type int8;
            }
            leaf connected-switches {
                type int32;
            }
            
        }
    }
}
